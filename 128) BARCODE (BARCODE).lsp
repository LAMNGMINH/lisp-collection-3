;AutoCAD bar code utility
;unknown origin, globalization by Xanadu.cz
(defun makebarsupc (txt)
 (setq txt (getcodeupc txt)
       cnt 1)
 (repeat 7 
  (setq digit (substr txt cnt 1))
  (cond
   ((and (= codetype 1) 
     (= digit "0")
    ) 
    (moveover)
   ) 
   ((and (= codetype 1) 
     (= digit "1")
    ) 
    (putline)
   ) 
   ((= digit "1") (moveover)) 
   ((= digit "0") (putline))
  ) 
  (setq cnt (1+ cnt))
 )
) 
(defun getcodeupc (txt)
 (cond
  ((= txt "0") (setq txt "0001101")) 
  ((= txt "1") (setq txt "0011001")) 
  ((= txt "2") (setq txt "0010011")) 
  ((= txt "3") (setq txt "0111101")) 
  ((= txt "4") (setq txt "0100011")) 
  ((= txt "5") (setq txt "0110001")) 
  ((= txt "6") (setq txt "0101111")) 
  ((= txt "7") (setq txt "0111011")) 
  ((= txt "8") (setq txt "0110111")) 
  ((= txt "9") (setq txt "0001011"))
 )
) 

(defun moveover () 
 (setq sp (polar sp a1 wid))
) 

(defun putline () 
 (moveover) 
 (command "_pline" sp "_w" wid wid (polar sp a2 ht) "")
) 

(defun getchecknum ()
 (if(= num1 num2)(setq checknum "0")(progn
 (setq pt1 (+ (atoi (substr num1 2 1))
              (atoi (substr num1 4 1))
              (atoi (substr num2 1 1))
              (atoi (substr num2 3 1)) 
              (atoi (substr num2 5 1))
           ))
 (setq pt2 (+ (atoi (substr num1 1 1))
              (atoi (substr num1 3 1))
              (atoi (substr num1 5 1))
              (atoi (substr num2 2 1)) 
              (atoi (substr num2 4 1))
           ))
 (setq pt1 (itoa(+ pt2 (* 3 pt1))))
 (setq checknum (itoa(- 10 (atoi(substr pt1 (strlen pt1) 1)))))
))
) 

(defun c:barcode ()
 (setvar "blipmode" 0)
 (setvar "cmdecho" 0)
 (setq syschr "0")
 (setq ht1 (* 0.5 (getvar "dimscale")) 
       ht2 (* 0.45 (getvar "dimscale")) 
       wid (* 0.0125 (getvar "dimscale"))
       ht ht1)
 (initget 1) 
 (setq sp (getpoint "\nBar Code Start Point: "))
 (initget 1) 
 (setq a1 (getangle sp "\nAngle for Bar Code: ") 
       a2 (+ a1 (* 0.5 pi)))
 (setq num1 100000 
       num2 100000)
 (while (>= num1 100000) 
  (initget 7) 
  (setq num1 (getreal "\nFirst Number(five digits): "))
 ) 
 (while (>= num2 100000) 
  (initget 7) 
  (setq num2 (getreal "\nSecond Number(five digits): "))
 ) 
 (repeat 8 
  (moveover)
 ) 
 (command "_text" "_j" "_r" (polar (polar sp (+ a2 pi) (* 3 wid)) (+ pi a1) 
                                (* 2 wid)
                         ) 
          (* 6 wid) a1 syschr
 ) 
 (putline) 
 (moveover) 
 (putline) 
 (setq codetype 1)
 (makebarsupc syschr)
 (setq txpt1 (polar (polar sp (+ a2 pi) (* 3 wid)) a1 (* 2 wid)))
 (setq sp (polar sp a2 (* 4 wid)) 
       ht ht2 
       num1 (rtos num1 2 0) 
       numcnt 1)
 (while (< (strlen num1) 5) 
  (setq num1 (strcat "0" num1))
 ) 
 (repeat 5 
  (makebarsupc (substr num1 numcnt 1))
  (setq numcnt (1+ numcnt))
 ) 
 (setq sp (polar sp (+ pi a2) (* 4 wid)) 
       ht ht1)
 (setq txpt2 (polar (polar sp (+ a2 pi) (* 3 wid)) (+ pi a1) wid))
 (moveover) 
 (putline) 
 (moveover) 
 (putline) 
 (moveover) 
 (setq txpt3 (polar (polar sp (+ a2 pi) (* 3 wid)) a1 wid))
 (setq sp (polar sp a2 (* 4 wid)) 
       ht ht2 
       codetype 2 
       num2 (rtos num2 2 0) 
       numcnt 1)
 (while (< (strlen num2) 5) 
  (setq num2 (strcat "0" num2))
 ) 
 (repeat 5 
  (makebarsupc (substr num2 numcnt 1))
  (setq numcnt (1+ numcnt))
 ) 
 (setq ht ht1 
       sp (polar sp (+ pi a2) (* 4 wid)))
 (setq txpt4 (polar (polar sp (+ a2 pi) (* 3 wid)) (+ pi a1) wid))
 (getchecknum) 
 (makebarsupc checknum)
 (putline) 
 (moveover) 
 (putline) 
 (command "_text" "_j" "_f" txpt1 txpt2 (* 6 wid) num1) 
 (command "_text" "_j" "_f" txpt3 txpt4 (* 6 wid) num2) 
 (command "_text" (polar (polar sp (+ a2 pi) (* 3 wid)) a1 (* 2 wid)) (* 6 wid) a1 
          checknum
 )
)
