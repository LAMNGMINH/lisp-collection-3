-----------------------------------------------------------------------------------------------------
; Duong han cong truong
(defun C:DX ( / )
       (setq p1 (getpoint "\nStart point : ") )
       (setq p2 (getpoint p1 "OK\nEnd point   : ") )
       (if (null a) (setq a 1.0))
       (setq _a (getdist (strcat "Ok\nDistance <" (rtos a 2 1) ">: ")))
       (if (/= _a nil) (setq a _a))
       (if (null b) (setq b 1.0))
       (setq _b (getdist (strcat "Ok\nLenght <" (rtos b 2 1) ">: ")))
       (if (/= _b nil) (setq b _b))
; Chieu cao duong han lay mac dinh bang 0,75 khoang cach
       (if (= b nil)
	   (setq b (* 0.75 a))
       )
       (setq l  (distance p1 p2) )
       (setq n  (fix ( / l a ) ) )
       (setq deltaX ( - (car p2) (car p1) ) )
       (setq deltaY ( - (cadr p2) (cadr p1) ) )
       (setq i 0)
; Luu bien he thong
       (setq osmodeold (getvar "osmode")) 
       (setq blipmodeold (getvar "blipmode")) 
; Undo phai de truoc lenh chinh bien he thong
       (command "_UNDO" "_GROUP")
       (setvar "OSMODE" 0)
       (setvar "BLIPMODE" 0)		
; Them mot vong lap cho i
       (while (<= i n )
        (setq x1 ( + (car p1) (* i (* (/ a l) deltaX )  
                              )
                 ) 
        )
        (setq y1 ( + (cadr p1) (* i (* ( / a l ) deltaY ) 
                               )
                 ) 
        )
        (setq p3 (list x1 y1) )
        (setq x2 ( + ( + x1 (* -1 (* b (/ deltaY l) ) ) ) (* b (/ deltaX l) )
        	)
        ) 
        (setq y2 ( + (+ y1 (* b (/ deltaX l) ) ) (* b (/ deltaY l) )
       	 )             
        )

        (setq p4 (list x2 y2) )

        (setq x5 ( + x1 (* -1 (* b (/ deltaY l) )
                        ) 
                 ) 
        ) 
        (setq y5 ( + y1 (* b (/ deltaX l) 
                        )
                 )
        ) 
        (setq p5 (list x5 y5) )
        (setq x6 ( + x1  (* b (/ deltaX l) 
                        ) 
                 ) 
        ) 
        (setq y6 ( + y1 (* b (/ deltaY l) 
                        )
                 )
        ) 
        (setq p6 (list x6 y6) )
        (command "LINE" p3 p4 "")
        (command "LINE" p5 p6 "")
        (setq i (+ i 1) )
       )
       (command "_UNDO" "_END")
; Khoi phuc lai cac bien he thong da thay doi
       (setvar "BLIPMODE" blipmodeold)		
       (setvar "OSMODE" osmodeold)
       (princ)
)
; Duong han cong truong net khuat
(defun C:DF ( / )
       (setq p1 (getpoint "\nStart point : ") )
       (setq p2 (getpoint p1 "OK\nEnd point   : ") )
       (if (null a) (setq a 1.0))
       (setq _a (getdist (strcat "Ok\nDistance <" (rtos a 2 1) ">: ")))
       (if (/= _a nil) (setq a _a))
       (if (null b) (setq b 1.0))
       (setq _b (getdist (strcat "Ok\nLenght <" (rtos b 2 1) ">: ")))
       (if (/= _b nil) (setq b _b))
; Chieu cao duong han lay mac dinh bang 0,75 khoang cach
       (if (= b nil)
	   (setq b (* 0.75 a))
       )
       (setq l  (distance p1 p2) )
       (setq n  (fix ( / l a ) ) )
       (setq deltaX ( - (car p2) (car p1) ) )
       (setq deltaY ( - (cadr p2) (cadr p1) ) )
       (setq i 0)
; Luu bien he thong
       (setq osmodeold (getvar "osmode")) 
       (setq blipmodeold (getvar "blipmode")) 
; Undo phai de truoc lenh chinh bien he thong
       (command "_UNDO" "_GROUP")
       (setvar "OSMODE" 0)
       (setvar "BLIPMODE" 0)		
; Them mot vong lap cho i
       (while (<= i n )
        (setq x1 ( + (car p1) (* i (* (/ a l) deltaX )  
                              )
                 ) 
        )
        (setq y1 ( + (cadr p1) (* i (* ( / a l ) deltaY ) 
                               )
                 ) 
        )
        (setq p3 (list x1 y1) )
        (setq x2 ( + ( + x1 (* -1 (* b (/ deltaY l) ) ) ) (* b (/ deltaX l) )
        	)
        ) 
        (setq y2 ( + (+ y1 (* b (/ deltaX l) ) ) (* b (/ deltaY l) )
       	 )             
        )

        (setq p4 (list x2 y2) )

        (setq x5 ( + x1 (* -1 (* b (/ deltaY l) )
                        ) 
                 ) 
        ) 
        (setq y5 ( + y1 (* b (/ deltaX l) 
                        )
                 )
        ) 
        (setq p5 (list x5 y5) )
        (setq x6 ( + x1  (* b (/ deltaX l) 
                        ) 
                 ) 
        ) 
        (setq y6 ( + y1 (* b (/ deltaY l) 
                        )
                 )
        ) 
        (setq p6 (list x6 y6) )
	(if (< (rem i 6) 4)        
	   	(progn
		 (command "LINE" p3 p4 "")
           	 (command "LINE" p5 p6 "")
		)
        ) 
	(setq i (+ i 1) )
       )
       (command "_UNDO" "_END")
; Khoi phuc lai cac bien he thong da thay doi
       (setvar "BLIPMODE" blipmodeold)		
       (setvar "OSMODE" osmodeold)
       (princ)
)
