**********************************************************
;;;PROGRAMME FOR CALCULATION BY P.M. PITALE !!!!!!!!!!!
**********************************************************

(defun c:ca ()
     (setq lu (getvar "luprec"))
     (setvar "luprec" 8)
(INITGET "+ * -")
(setq tx (getkword "\n\t+ | * | - ..... : "))
(cond ((= tx "+") 
     (setq lst (ssget))
     (setq n1 (sslength lst))
     (setq p1 (cdr (assoc 1 (entget (ssname lst 0)))))
     (setq t1 (atof p1))
     (setq p2 (cdr (assoc 1 (entget (ssname lst 1)))))
     (setq t2 (atof p2))
     (setq s1 (+ t1 t2)) 
     (setq n 2)
(repeat (- N1 2)
     (setq p3 (cdr (assoc 1 (entget (ssname lst n)))))
     (setq t3 (atof p3))
     (setq s2 (+ s1 t3))
     (setq s1 s2)
     (setq n (1+ n))
)
(PROMPT (STRCAT "\n\tTOTAL = " (rtos S1)))
;(setq s3 (STRCAT "TOTAL = " (rtos S1)))   ;;;(If You Want Text As "TOTAL = 2323" Then Replace (RTOS s1) as S3 in Line No. 26...)
(initget "Yes No")
(setq ans (getkword "\nDo You Want To Write Text Y/N <N> : "))
(if (= ans "Yes")
         (progn (setq ip (getpoint "\nText Insertion Point : "))
                (command "text" ip "" 0 (RTOS s1))
))
)
    ((= tx "*")
     (setq lst (ssget))
     (setq n1 (sslength lst))
     (setq p1 (cdr (assoc 1 (entget (ssname lst 0)))))
     (setq t1 (atof p1))
     (setq p2 (cdr (assoc 1 (entget (ssname lst 1)))))
     (setq t2 (atof p2))
     (setq s1 (* t1 t2)) 
     (setq n 2)
(repeat (- N1 2)
     (setq p3 (cdr (assoc 1 (entget (ssname lst n)))))
     (setq t3 (atof p3))
     (setq s2 (* s1 t3))
     (setq s1 s2)
     (setq n (1+ n))
)
(PROMPT (STRCAT "\n\tTOTAL = " (rtos S1)))
;(setq s3 (STRCAT "TOTAL = " (rtos S1)))   ;;;(If You Want Text As "TOTAL = 2323" Then Replace (RTOS s1) as S3 in Line No. 26...)
(initget "Yes No")
(setq ans (getkword "\nDo You Want To Write Text Y/N <N> : "))
(if (= ans "Yes")
         (progn (setq ip (getpoint "\nText Insertion Point : "))
                (command "text" ip "" 0 (RTOS s1))
))
)
    ((= tx "-")
     (setq lst (ssget))
     (setq n1 (sslength lst))
     (setq p1 (cdr (assoc 1 (entget (ssname lst 0)))))
     (setq t1 (atof p1))
     (setq p2 (cdr (assoc 1 (entget (ssname lst 1)))))
     (setq t2 (atof p2))
     (setq s1 (- t1 t2)) 
     (setq n 2)
(repeat (- N1 2)
     (setq p3 (cdr (assoc 1 (entget (ssname lst n)))))
     (setq t3 (atof p3))
     (setq s2 (- s1 t3))
     (setq s1 s2)
     (setq n (1+ n))
)
(PROMPT (STRCAT "\n\tTOTAL = " (rtos S1)))
;(setq s3 (STRCAT "TOTAL = " (rtos S1)))   ;;;(If You Want Text As "TOTAL = 2323" Then Replace (RTOS s1) as S3 in Line No. 26...)
(initget "Yes No")
(setq ans (getkword "\nDo You Want To Write Text Y/N <N> : "))
(if (= ans "Yes")
         (progn (setq ip (getpoint "\nText Insertion Point : "))
                (command "text" ip "" 0 (RTOS s1))
))
)
)
(setvar "luprec" lu)
(princ))
; (PROMPT "\nBY P.M.PITALE")
(PRINC)
(PROMPT "\n\t\tLoading Programme 
                Start Programme with [ CAL ] .. BY P.M.PITALE")
(princ)
