(defun c:vxl ()
  (setq limcheck-alt (getvar "limcheck"))
  (command "_ucs" "_d" "test7654321")
  (command "_UCS" "_S" "test7654321")
  (command "_UCS" "_w") 
  (setvar "limcheck" 0)
  (setq el (entsel "\nchoose object: "))
  (setq ele (entget (car el))) 
   (setq p1 (cdr (assoc 10 ele)))
  (command "_move" el "" p1 "0,0")
  (command "_zoom" "_C" "0,0" "")
  (setq dist (getdist "\noffset distance: "))
  (command "_offset" dist el pause "")
  (command "_move" el "_l" "" "0,0" p1)
  (command "_zoom" "_P")
  (command "_ucs" "_r" "test7654321")
  (command "_ucs" "_d" "test7654321")  
  (setvar "limcheck" limcheck-alt)
  (princ "\nReady!")
  (princ)

)
(princ "\nLoaded workaround for offset. Start with VXL")
(princ)
